FME workspace skrypt.fmw

Parameters:
- DestDataset_SHAPEFILE_3 = $(FME_MF_DIR)wyniki zad.A   # Destination Esri Shapefile Folder
- DestDataset_SHAPEFILE = $(FME_MF_DIR)wyniki   # Destination Esri Shapefile Folder
- SourceDataset_FFS_5 = $(FME_MF_DIR)Dane\TBD\TBD.ffs   # Source FME Feature Store (FFS) File(s)
- DestDataset_OGCKML_4 = $(FME_MF_DIR)wyniki zad.B\Najkrótsza trasa.kml   # Destination Google KML File
- SourceDataset_CSV2_3 = $(FME_MF_DIR)Dane\NMT100\NMT100.txt   # Source CSV (Comma Separated Value) File(s)
- SourceDataset_FFS_4 = $(FME_MF_DIR)Dane\TBD\TBD.ffs   # Source FME Feature Store (FFS) File(s)

Readers:
- FFS_2: FFS from $(SourceDataset_FFS_5)
- CSV2_2: CSV2 from $(SourceDataset_CSV2_3) in ETRS89.PolandCS92
- FFS_3: FFS from $(SourceDataset_FFS_4)

Writers:
- SHAPEFILE_1: SHAPEFILE to $(DestDataset_SHAPEFILE)
- SHAPEFILE_2: SHAPEFILE to $(DestDataset_SHAPEFILE_3) in EPSG:2180
- OGCKML_3: OGCKML to $(DestDataset_OGCKML_4) in ETRS89.PolandCS92

Bookmark: Zadanie A
Note: Wczytanie danych do NMT. Uklad wspolrzednych zostal ustawiony na ETRS89.PolandCS92, poniewaz dane o budynkach sa w takim ukladzie
Note: Wczytanie danych o budynkach. Uklad wspolrzednych jest czytany z wybranch plikow. Okazuje sie ze dane sa w ukladzie ETRS89.PolandCS92
CSV (reader CSV2_2)
    attributes: 430700.00 real64, 437800.00 real64, 118.62 real32
    -> AttributeManager
Note: Zmiana nazw kolumn
AttributeManager
    ATTR_TABLE:
      RENAME_SET_VALUE 430700.00 > Wsp. X (real64)
      RENAME_SET_VALUE 437800.00 > Wsp. Y (real64)
      RENAME_SET_VALUE 118.62 > Wsp. H (real32)
    -> VertexCreator
Note: Stworzenie punktów na podstawie współrzędnych. W "Mode" wybieramy "Replace with Point". Sa one niezbedne, poniewaz kolejny transformer potrzebuje punktow, a nie wspolrzednych
VertexCreator
    MEASURE_TYPE = Continuous
    MODE_NAME = Replace with Point
    XVAL = @Value(Wsp. X)
    YVAL = @Value(Wsp. Y)
    ZVAL = @Value(Wsp. H)
    -> SurfaceDraper [POINTS/LINES]
TBD_BUDYNKI (reader FFS_3)
    attributes: ID number(38,0), ID_IMPORTU number(38,0), ID_TYPU number(38,0), ID_FUNKCJI_OGOLNEJ number(38,0), ID_FUNKCJI_SZCZEGOLOWEJ number(38,0)
    -> SpatialFilter [Candidate]
TBD_MIEJSCOWOSCI (reader FFS_3)
    attributes: ID number(38,0), ID_IMPORTU number(38,0), ID_TYPU number(38,0), NAZWA varchar(255), GMINA_TERYT varchar(7), GMINA_NAZWA varchar(255), ID_PRNG varchar(38), LICZBA_MIESZKANCOW int32
    -> TestFilter
Note: Wyselekcjonowanie Kalisza jako miejscowości potrzebnej w transformerze SpatialFilter
TestFilter
    DEFAULT_VALUE = <UNFILTERED>
    PASSED_TEST_GROUP_OUTPUT = FIRST
    TEST_LIST = "BOOL_OP,OR,COMPOSITE_TEST,""""""1"""""",TEST_CLAUSE,TEST @Value(NAZWA) = Kalisz",@Value(NAZWA) = Kalisz
    @Value(NAZWA) = Kalisz -> SpatialFilter [Filter]
Note: Wyselekcjonowanie budynków, które znajduja się na terytorium Kalisza. / Jako "Spatatial Predicates to Test" ustawiamy "Filter OGC-Contains Candidate" - chodzi o to by Kalisz zawieral budynki
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> SpatialFilter_2 [Candidate]
TBD_OBREB (reader FFS_3)
    attributes: ID number(38,0), ID_IMPORTU number(38,0), ID_TYPU number(38,0), GMINA_TERYT varchar(7), GMINA_NAZWA varchar(255), NR_OBREBU varchar(13)
    -> Tester_2
Note: Wyselekcjonowanie obrębów, które sa w Kaliszu. Sprawdzamy czy gmina danego obrebu to Kalisz
Tester_2
    BOOL_OP = OR
    TEST_CLAUSE = TEST @Value(GMINA_NAZWA) = Kalisz
    TEST_MODE = TEST
    PASSED -> SpatialFilter_2 [Filter]
Note: Dodanie informacji o obrębach, w których znajduja się budynki
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> SurfaceDraper [DRAPE_FEATURES]
Note: Stworzenie NMT. / Jako "Points/Lines' dajemy poprzednio stworzone punkty. / Jako "DrapeFeatures" dajemy budynki, ktore sa w Kaliszu. / "Surface Tolerance" ustawiamy na 0
SurfaceDraper
    ADDZ_TYPE = Replace Z
    DRAPE_TYPE = VERTEX
    INTERPOLATION_TYPE = AUTO
    TOLERANCE = 0
    DRAPED_FEATURES -> Extruder
Note: Wypietrzenie budynkow na takie wysokosci, jakie sa przypisane do poszczegolnych wierzchołkow budynkow - jako "Distance" ustawiamy wartosc wspolrzednej Z
Extruder
    DIRECTION = Auto
    DISTANCE = @ZValue()
    EXTRUDED -> BoundsExtractor
Note: Znalezienie najmniejszych i najwiekszych współrzednych
BoundsExtractor
    XMAX = _xmax
    XMIN = _xmin
    YMAX = _ymax
    YMIN = _ymin
    ZMAX = _zmax
    ZMIN = _zmin
    -> Tester
Note: Wyselekcjonowanie budynków, które znajduja sie powyzej 121 m. Chcemy by caly budynek byl powyzej danej wysokosci, wiec ustawiamy aby minimalna wspolrzedna Z byla wieksza niz 121
Tester
    BOOL_OP = OR
    TEST_CLAUSE = TEST @Value(_zmin) > 121
    TEST_MODE = TEST
    PASSED -> Shapefile1 (writer SHAPEFILE_2)
Note: Zapis buydnków do osobnych plików shp w zależności od obrebu z odpowiednimi atrybutami. / Jako"Output Dimension" ustawiamy 3D +Measures, bo chcemy miec dane 3d a nie plaskie
Shapefile1 (writer SHAPEFILE_2)
    attributes: ID Budynku number(38,0), ID Obrebu varchar(13), Min_ wys_ double, Nr indeksu double, Data Wykon varchar(20)

Bookmark: Zadanie B
Note: Wczytanie danych. Uklad wspolrzednych zostaje wczytany ze zrodla - jest nim ETRS98.PolandCS92
TBD_OBREB (reader FFS_2)
    attributes: ID number(38,0), ID_IMPORTU number(38,0), ID_TYPU number(38,0), GMINA_TERYT varchar(7), GMINA_NAZWA varchar(255), NR_OBREBU varchar(13)
    -> GeometryExtractor
Note: Wydobycie geometrii obrębów i zapisanie jej w tabeli atrybutów. Nie zmieniamy parametru "Geometry Encoding", zostaje on jako "FME Binary"
GeometryExtractor
    ATTR = _geometry
    KIND_LONG = FME Binary
    REMOVE_GEOMETRY = No
    -> GeometryCoercer
Note: Zmiana typu geometrii na linie- jako "Geometry Type" wybieramy "fme_line"
GeometryCoercer
    GQUERY:
      for $geom in //geometry
      where $geom/count(parent::geometry) = 0
      return number($geom/@fme_id)
    KIND = fme_line
    COERCED -> TopologyBuilder
Note: Stworzenie sieci topologicznej
TopologyBuilder
    ALLOW_CYCLES = No
    BOUNDING_EDGES = All
    CLEANING_TOLERANCE = Automatic
    DEAGGREGATE_INPUT = Yes
    GENERATION_MODE = INTERSECT
    MAX = 0
    OVERLAPPING_MODE = No
    NODE -> CoordinateExtractor
    LINE -> ShortestPathFinder [NETWORK]
Note: Wydobycie współrzędnych węzłów
CoordinateExtractor
    IND = 0
    MODE = Specify Coordinate
    X_ATTR = _x
    Y_ATTR = _y
    Z_ATTR = _z
    -> StatisticsCalculator
    -> TestFilter_2
Note: Znalezienie największych i najmniejszych wartości wspólrzędnych. Wykorzystamy je w filtorwaniu węzłów
StatisticsCalculator
    ATTR_ACCUM_MODE = None
    CALCULATION_MODE = NUMERIC
    FEAT_STATS = _x,NUMERIC_MODE,MIN,MAX,,,,,,,,,,,
Note: Wyselekcjonowanie punktów położonych najbardziej na wschód i zachód
TestFilter_2
    DEFAULT_VALUE = <UNFILTERED>
    PASSED_TEST_GROUP_OUTPUT = FIRST
    TEST_LIST:
      "BOOL_OP,OR,COMPOSITE_TEST,""""""1 OR 2"""""",TEST_CLAUSE,TEST @Value(_x) = 430633.08
      TEST @Value(_x) = 451937.86",@Value(_x) = 430633.08
    @Value(_x) = 430633.08 -> LineBuilder
Note: Stworzenie linii między punktami
LineBuilder
    ACCUM_INPUT_ATTRS = Use Attributes From One Feature
    REMOVE_DUPLICATES = No
    LINE -> ShortestPathFinder [FROM-TO]
    LINE -> LengthCalculator
Note: Znalezienie najkrotszej sciezki mniedzy dwoma punktami
ShortestPathFinder
    ALLOW_UTURNS = Yes
    REORDER_MODE = NONE
    SNAP_POINTS = Yes
    SNAP_TOLERANCE = 0
    WEIGHT_ATTR_CHOICE = BY_LENGTH
    PATH -> FeatureMerger [REQUESTOR]
Note: Obliczenie długości linii między punktami w linii prostej
LengthCalculator
    DIM = 2
    LEN_ATTR = _length
    MULT = 1
    -> FeatureMerger [SUPPLIER]
Note: Połaczenie danych o dwóch odległościach
FeatureMerger
    ATTR_ACCUM_MODE = Merge Supplier
    ATTR_CONFLICT_RES = Use Requestor
    IGNORE_NULLS = No
    JOIN_KEYS = @Value(_node_number) @Value(_node_number) AUTO
    MERGE_TYPE = Attributes Only
    PROCESS_DUPS = NO
    REJECT_NULL_MISSING_KEYS = No
    SUPPLIERS_FIRST = No
    MERGED -> AttributeManager_2
Note: Usunięcie niepotrzebnych atrybutów, zmiana wartosci z metrów na kilometry,dodanie nowych atrybutów z różnica długości i imienie i nazwiskiem
AttributeManager_2
    ATTR_TABLE:
      REMOVE ID (number(38,0))
      REMOVE ID_IMPORTU (number(38,0))
      REMOVE ID_TYPU (number(38,0))
      REMOVE GMINA_TERYT (varchar(7))
      REMOVE GMINA_NAZWA (varchar(255))
      REMOVE NR_OBREBU (varchar(13))
      REMOVE _geometry (buffer)
      REMOVE _node_number (uint32)
      REMOVE _x (real64)
      REMOVE _y (real64)
      REMOVE _z (real64)
      RENAME_SET_VALUE _total_cost > Długość trasy (buffer) = @Evaluate(@Value(Długość trasy)/1000)
      RENAME_SET_VALUE _length > Odległość w linii prostej (real64) = @Evaluate(@Value(Odległość w linii prostej)/1000)
      RENAME_SET_VALUE Różnica długośći > Różnica długości [km] (varchar(200)) = @Evaluate(@abs(@Value(Długość trasy))-@Value(Odległość w linii prostej)))
      SET_TO Imię i nazwisko (varchar(200)) = Julia Gomulska
    USER_EXPOSED_ATTRIBUTES = Różnica długośći,Nr indeksu,Imię i nazwisko
    -> NewFeatureType (writer OGCKML_3)
NewFeatureType (writer OGCKML_3)
    attributes: Długość trasy kml_char(255), Odległość w linii prostej kml_real64, Różnica długości [km] kml_char(200), Imię i nazwisko kml_char(200)
