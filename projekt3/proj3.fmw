FME workspace proj3.fmw

Parameters:
- SourceDataset_WFS_3 = https://wfs.bdl.lasy.gov.pl/geoserver/BDL/ows   # Source WFS (Web Feature Service) URL
- SourceDataset_WFS = https://wfs.bdl.lasy.gov.pl/geoserver/BDL/ows   # Source WFS (Web Feature Service) URL
- DestDataset_GML =   # Destination Geography Markup Language (GML) File
- DestDataset_OGCKML =   # Destination Google KML File

Readers:
- WFS_2: WFS from $(SourceDataset_WFS_3)
- WFS_1: WFS from $(SourceDataset_WFS)

Writers:
- GML_1: GML to $(DestDataset_GML)
- GML_2: GML to $(FME_MF_DIR)3projwynik\plikgml.gml
- OGCKML_1: OGCKML to $(DestDataset_OGCKML)
- OGCKML_2: OGCKML to $(FME_MF_DIR)3projwynik\plikkml.kml

RDLP_Warszawa_wydzielenia (reader WFS_1)
    attributes: gml_parent_id xml_buffer, gml_parent_property xml_buffer, gml_id xml_buffer, geom xml_geometry, a_i_num xml_int64, a_i_num.xsi_nil xml_boolean, adr_for xml_buffer, adr_for.xsi_nil xml_boolean, area_type xml_buffer, area_type.xsi_nil xml_boolean, site_type xml_buffer, site_type.xsi_nil xml_boolean, silvicult xml_buffer, silvicult.xsi_nil xml_boolean, forest_fun xml_buffer, forest_fun.xsi_nil xml_boolean, stand_stru xml_buffer, stand_stru.xsi_nil xml_boolean, rotat_age xml_int64, rotat_age.xsi_nil xml_boolean, sub_area xml_real64, sub_area.xsi_nil xml_boolean, prot_categ xml_buffer, prot_categ.xsi_nil xml_boolean, species_cd xml_buffer, species_cd.xsi_nil xml_boolean, part_cd xml_buffer, part_cd.xsi_nil xml_boolean, spec_age xml_int64, spec_age.xsi_nil xml_boolean,
      a_year xml_int64, a_year.xsi_nil xml_boolean, nazwa xml_buffer, nazwa.xsi_nil xml_boolean
    -> Tester_3
Note: wybranie drzewostanow
Tester_3
    BOOL_OP = OR
    TEST_CLAUSE = TEST @Value(area_type) = D-STAN
    TEST_MODE = TEST
    PASSED -> SpatialFilter_3 [Candidate]
Nadleśnictwa (reader WFS_2)
    attributes: gml_parent_id xml_buffer, gml_parent_property xml_buffer, gml_id xml_buffer, geom xml_geometry, adress_forest xml_buffer, adress_forest.xsi_nil xml_boolean, a_year xml_int64, a_year.xsi_nil xml_boolean, inspectorate_name xml_buffer, inspectorate_name.xsi_nil xml_boolean, region_cd xml_buffer, region_cd.xsi_nil xml_boolean, inspectorate_cd xml_buffer, inspectorate_cd.xsi_nil xml_boolean
    -> Tester_2
Note: wybranie nadlesnictw, ktore sa w obrebie wybranego wydzielenia
Tester_2
    BOOL_OP = OR
    TEST_CLAUSE = TEST @Value(region_cd) = 17
    TEST_MODE = TEST
    PASSED -> Sampler_2
Note: wybranie jednego nadlesnictwa
Sampler_2
    RATE = 1
    SAMPLE_MODE = No
    SAMPLE_TYPE_LONG = First N Features
    SAMPLED -> SpatialFilter_3 [Filter]
Note: wybranie drzewostanów ktore sa w obszarze nadlesnictwa
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> FeatureMerger_2 [REQUESTOR]
Creator
    GEOMTYPE = Geometry Object
    NUM = 1
    CREATED -> RandomNumberGenerator_3
Note: wygenerowanie liczb okreslajacych przedzial wiekowy
RandomNumberGenerator_3
    MAX = 70
    MIN = 30
    PLACES = 0
    RESULT_ATTR = _random_number_min
    -> RandomNumberGenerator_4
RandomNumberGenerator_4
    MAX = 120
    MIN = 80
    PLACES = 0
    RESULT_ATTR = _random_number_max
    -> FeatureMerger_2 [SUPPLIER]
Note: dolaczenie informacji o wylosowanych liczbach
FeatureMerger_2
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Tester_4
Note: wybranie dzrzewostanow ktorych wiek zawiera sie w odpowiednim zakresie
Tester_4
    BOOL_OP = AND
    TEST_CLAUSE:
      TEST @Value(spec_age) >= @Value(_random_number_min)
      TEST @Value(spec_age) <= @Value(_random_number_max)
    TEST_MODE = TEST
    PASSED -> AttributeManager
    PASSED -> AttributeManager_2
Note: usuniecie pustych atrybutow
AttributeManager_2
    ATTR_TABLE:
      REMOVE gml_parent_id (buffer)
      REMOVE geom (buffer)
      REMOVE adress_forest (buffer)
      REMOVE adress_forest.xsi_nil (logical)
      REMOVE a_year.xsi_nil (logical)
      REMOVE inspectorate_name (buffer)
      REMOVE inspectorate_name.xsi_nil (logical)
      REMOVE region_cd (buffer)
      REMOVE region_cd.xsi_nil (logical)
      REMOVE inspectorate_cd (buffer)
      REMOVE inspectorate_cd.xsi_nil (logical)
      REMOVE a_i_num.xsi_nil (logical)
      REMOVE adr_for.xsi_nil (logical)
      REMOVE area_type.xsi_nil (logical)
      REMOVE site_type.xsi_nil (logical)
      REMOVE silvicult.xsi_nil (logical)
      REMOVE forest_fun.xsi_nil (logical)
      REMOVE stand_stru.xsi_nil (logical)
      REMOVE rotat_age.xsi_nil (logical)
      REMOVE sub_area.xsi_nil (logical)
      REMOVE prot_categ.xsi_nil (logical)
      REMOVE species_cd.xsi_nil (logical)
      REMOVE part_cd.xsi_nil (logical)
      REMOVE spec_age.xsi_nil (logical)
      REMOVE nazwa.xsi_nil (logical)
      REMOVE _predicate (buffer)
      REMOVE _creation_instance (uint64)
      REMOVE _random_number_min (real64)
      REMOVE _random_number_max (real64)
    -> NewFeatureType (writer GML_2)
NewFeatureType (writer GML_2)
    attributes: a_year xml_int64, a_i_num xml_int64, adr_for xml_buffer, area_type xml_buffer, site_type xml_buffer, silvicult xml_buffer, forest_fun xml_buffer, stand_stru xml_buffer, rotat_age xml_int64, sub_area xml_real64, prot_categ xml_buffer, species_cd xml_buffer, part_cd xml_buffer, spec_age xml_int64, nazwa xml_buffer
Note: dostosowanie atrybutow
AttributeManager
    ATTR_TABLE:
      REMOVE gml_parent_id (buffer)
      REMOVE gml_parent_property (buffer)
      REMOVE gml_id (buffer)
      REMOVE geom (buffer)
      REMOVE adress_forest (buffer)
      REMOVE adress_forest.xsi_nil (logical)
      REMOVE a_year (int64)
      REMOVE a_year.xsi_nil (logical)
      REMOVE inspectorate_name (buffer)
      REMOVE inspectorate_name.xsi_nil (logical)
      REMOVE region_cd (buffer)
      REMOVE region_cd.xsi_nil (logical)
      REMOVE inspectorate_cd (buffer)
      REMOVE inspectorate_cd.xsi_nil (logical)
      REMOVE a_i_num (int64)
      REMOVE a_i_num.xsi_nil (logical)
      REMOVE adr_for (buffer)
      REMOVE adr_for.xsi_nil (logical)
      REMOVE area_type (buffer)
      REMOVE area_type.xsi_nil (logical)
      RENAME_SET_VALUE site_type > Typ siedliska (buffer)
      REMOVE site_type.xsi_nil (logical)
      REMOVE silvicult (buffer)
      REMOVE silvicult.xsi_nil (logical)
      REMOVE forest_fun (buffer)
      REMOVE forest_fun.xsi_nil (logical)
      REMOVE stand_stru (buffer)
      REMOVE stand_stru.xsi_nil (logical)
      REMOVE rotat_age (int64)
      REMOVE rotat_age.xsi_nil (logical)
      RENAME_SET_VALUE sub_area > Powierzchnia [ha] (real64)
      REMOVE sub_area.xsi_nil (logical)
      RENAME_SET_VALUE prot_categ > Pod ochrona? (buffer) = FME_CONDITIONAL:DEFAULT_VALUE'Nie'BOOL_OP;OR;COMPOSITE_TEST;1 OR 2 OR 3 OR 4;TEST @Value(Pod ochrona?) = OCH BADAW;TEST @Value(Pod ochrona?) = OCH GLEB;TEST @Value(Pod ochrona?) = OCH OSTOJ;TEST @Value(Pod ochrona?) = OCH WOD'Tak 'FME_NUM_CONDITIONS2___
      REMOVE prot_categ.xsi_nil (logical)
      REMOVE species_cd (buffer)
      REMOVE species_cd.xsi_nil (logical)
      REMOVE part_cd (buffer)
      REMOVE part_cd.xsi_nil (logical)
      RENAME_SET_VALUE spec_age > Wiek (int64)
      REMOVE spec_age.xsi_nil (logical)
      REMOVE nazwa (buffer)
      REMOVE nazwa.xsi_nil (logical)
      REMOVE _predicate (buffer)
      REMOVE _creation_instance (uint64)
      REMOVE _random_number_min (real64)
      REMOVE _random_number_max (real64)
      SET_TO Autor (buffer) = Julia Gomulska
    -> KMLPropertySetter
Note: tworzenie tabeli opisowej KML
KMLPropertySetter
    ADD_ATTR_TABLE = Yes
    ATTR_TABLE_TITLE = Atrybuty
    CONTENT_TYPE = Text
    EXTRUDE = No
    GEOM_TYPE = Vector
    NAME = <auto>
    SUMMARY = <none>
    TESSELATE = Yes
    VISIBILITY = Yes
    -> KMLStyler
Note: Wizualna stylizacja
KMLStyler
    COLOR = 0.721569,0.482353,0.721569
    FILL_COLOR = 1,1,1
    FILL_OPACITY = 0.4
    ICON_OPACITY = 1.0
    ICON_SCALE = 0.8
    LABEL_OPACITY = 1.0
    LABEL_SCALE = 1.0
    LABEL_VISIBILITY = Yes
    LINE_WIDTH = 2.0
    LINE_WIDTH_UNITS = Pixels (Display Units)
    OPACITY = 1.0
    STYLE_PER_FEATURE = Yes
    KMLStyled -> NewFeatureType (writer OGCKML_2)
NewFeatureType (writer OGCKML_2)
    attributes: Typ siedliska kml_char(255), Powierzchnia [ha] kml_real64, Pod ochrona? kml_char(255), Wiek kml_char(20), Autor kml_char(255)
